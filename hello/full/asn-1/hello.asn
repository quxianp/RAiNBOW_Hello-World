// ASN.1 - Hello World! :: RAiNBOW_Hello-World
//   colour     : not assigned by Linguist
//   layer      : full (byte-balanced rainbow bar)
//   upstream   : https://github.com/quxianp/RAiNBOW_Hello-World
//   reference  : see https://esolangs.org/ and https://rosettacode.org/

HelloWorld DEFINITIONS ::= BEGIN
    greeting IA5String ::= "Hello World!"
END
